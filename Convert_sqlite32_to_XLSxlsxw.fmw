FME workspace Convert_sqlite32_to_XLSxlsxw.fmw

Parameters:
- SourceDataset_SQLITE3 = $(FME_MF_DIR)mining_companies.db   # SQLite Database
- DestDataset_XLSXW = $(FME_MF_DIR)mining_companies_XLS_snaphot_21032025.xlsx   # Destination Microsoft Excel File

Readers:
- SQLITE3_1: SQLITE3 from $(SourceDataset_SQLITE3)

Writers:
- XLSXW_1: XLSXW to $(DestDataset_XLSXW)

Bookmark: Reader Feature Types
companies (reader SQLITE3_1)
    attributes: company_id integer, tsx_code text,Unique, company_name text, name_alt text, status text, headquarters text, minerals_of_interest text, percent_gold double, percent_silver double, description text, last_updated text
    -> companies (writer XLSXW_1)

Bookmark: Writer Feature Types
companies (writer XLSXW_1)
    attributes: company_id number(20), tsx_code string(20), company_name string(20), name_alt string(20), status string(20), headquarters string(20), minerals_of_interest string(20), percent_gold number(20), percent_silver number(20), description string(20), last_updated string(20)
